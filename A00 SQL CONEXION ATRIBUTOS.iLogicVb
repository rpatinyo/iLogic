' <FireOthersImmediately>False</FireOthersImmediately>
AddReference "System.Data"
AddReference "System.Core"
AddReference "System.Xml"
Imports System.Data.Odbc
Imports System.Data.OleDb
Imports System.data

Sub main
iProperties.Value("Custom", "CODIGO_DESCRIPCION") = Parameter("CODIGO_DESCRIPCION")
CODIGO_DESCRIPCION = iProperties.Value("Custom", "CODIGO_DESCRIPCION")
LARGO = Len(CODIGO_DESCRIPCION)
CODIGO_CONFIG = Left(CODIGO_DESCRIPCION, 17)
DESCRIPCION = Mid(CODIGO_DESCRIPCION, 21, (LARGO - 20))
CODIGO = Left(CODIGO_CONFIG, 10)
If Left(CODIGO, 3) <> "A00" Then
	MessageBox.Show("CÓDIGO NO VÁLIDO", "ERROR")
	iProperties.Value("Custom", "CODIGO_CONFIG") = ""
	iProperties.Value("Custom", "DESCRIPCION") = ""
	iProperties.Value("Project", "Description") = ""
	iProperties.Value("Custom", "CATEGORIA") = ""
	iProperties.Value("Custom", "NOTAS") = ""
	Return
End If
'Logger.Info(records1(245).Values(3).Replace(vbCr, "").Replace(vbLf, " "))
iLogicVb.RunExternalRule("INSCA PESO ENSAMBLAJE")
	
PARAMETER("CODIGO_CONFIG") = CODIGO_CONFIG
PARAMETER("DESCRIPCION") = DESCRIPCION
iProperties.Value("Custom", "CODIGO_CONFIG") = CODIGO_CONFIG
iProperties.Value("Custom", "DESCRIPCION") = DESCRIPCION
iProperties.Value("Project", "Description") = DESCRIPCION

parameter("TSQL") = "product_category"
parameter("PAR") = "CATEGORIA"
parameter("CSQL") = "complete_name"
parameter("SQL") = "Select product_template.default_code " &
", product_template.name " &
", product_template.description " &
", product_category.complete_name " &
"From product_template INNER Join product_category On product_template.categ_id = product_category.id " &
"Where (((product_template.technical_office)='1') AND product_template.default_code = '" & parameter("CODIGO_CONFIG") & "') " &
"Order By product_template.default_code;"

con2(parameter("TSQL"), parameter("PAR"), parameter("CSQL"), parameter("SQL"))

parameter("TSQL") = "product_template"
parameter("PAR") = "NOTAS"
parameter("CSQL") = "description"
parameter("SQL") = "Select product_template.description " &
"From product_template INNER Join product_category On product_template.categ_id = product_category.id " &
"Where (((product_template.technical_office)='1') AND product_template.default_code = '" & parameter("CODIGO_CONFIG") & "') " &
"Order By product_template.default_code;"

con3(parameter("TSQL"), parameter("PAR"), parameter("CSQL"), parameter("SQL"))

parameter("TSQL") = "product_template"
parameter("PAR") = "VAULT_ID"
parameter("CSQL") = "vault_internal_id"
parameter("SQL") = "Select product_product.default_code" &
", product_template.vault_internal_id" &
", product_product.active " &
"From product_product INNER Join product_template On product_product.product_tmpl_id = product_template.id " &
"Where (((product_product.default_code)= '" & parameter("CODIGO_CONFIG") & "') AND (product_product.active = '1')) " &
"Order By product_template.vault_internal_id DESC;"

con4(parameter("TSQL"), parameter("PAR"), parameter("CSQL"), parameter("SQL"))		
End Sub


Sub con2(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList

	For Each row In t1.Rows
		
     nombre.Add(row(campo))

	Next
	
	MultiValue.List(iProp) = nombre
			
	iProperties.Value("Custom", "CATEGORIA")= nombre(0)
	parameter("CATEGORIA") = iProperties.Value("Custom", "CATEGORIA")
	final = Len(iProperties.Value("Custom", "CATEGORIA"))
	Extraccion = final - 13
	Categ = Mid(iProperties.Value("Custom", "CATEGORIA"), 14, Extraccion)
	iProperties.Value("Custom", "00 Categoria PTERMINADO") = Categ
	'Se modifica el campo de Odoo "technical_office"
	'iProperties.Value("Custom", "technical_office") = "0"
	'Se asigna a la categoría de Vault "Ingeniería"
	iProperties.Value("Custom", "VDS_Category") = "Ingeniería"
	'Se desactiva el esquema de numeración
	iProperties.Value("Custom", "VDS_NumSchm") = ""
		
End Sub

Sub con3(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList
	
	nombre.Clear()
	MultiValue.List(iProp) = nombre
	
	For Each row In t1.Rows
		nombre.Add(row(campo))
		'Logger.Debug("notas = {0}", nombre(0).ToString)
	Next
	
	If nombre(0).ToString = "" Then
		iProperties.Value("Custom", "NOTAS") = "N/A"
	ElseIf nombre(0).ToString <> "" Then
		iProperties.Value("Custom", "NOTAS") = nombre(0).ToString
	End If
	
	MultiValue.List(iProp) = nombre
		
	parameter("NOTAS") = iProperties.Value("Custom", "NOTAS")
	
End Sub

Sub con4(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList
	
	nombre.Clear()
	MultiValue.List(iProp) = nombre
	
	For Each row In t1.Rows
		nombre.Add(row(campo))
		'Logger.Debug("notas = {0}", nombre(0).ToString)
	Next
	
	If nombre(0).ToString = "" Then
		iProperties.Value("Custom", "VAULT_ID") = "0"
	ElseIf nombre(0).ToString <> "" Then
		iProperties.Value("Custom", "VAULT_ID") = nombre(0).ToString
	End If
	
	MultiValue.List(iProp) = nombre
		
	parameter("VAULT_ID") = iProperties.Value("Custom", "VAULT_ID")
	
	
	If iProperties.Value("Custom", "VAULT_ID") <> "0" Then
		iProperties.Value("Custom", "BANNER") = "EL PRODUCTO YA SE HA DIBUJADO ANTERIORMENTE. CONSULTAR VAULT"
		Else
			iProperties.Value("Custom", "BANNER") = ""
	End If

	
End Sub
