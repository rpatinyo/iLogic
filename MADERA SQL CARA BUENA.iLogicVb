' <FireOthersImmediately>False</FireOthersImmediately>
AddReference "System.Data"
AddReference "System.Core"
AddReference "System.Xml"
Imports System.Data.Odbc
Imports System.Data.OleDb
Imports System.data

Dim oDoc As PartDocument
oDoc = ThisDoc.Document

Dim undo As Transaction
undo = ThisApplication.TransactionManager.StartTransaction(oDoc,"Cara buena")

oComp = oDoc.ComponentDefinition

Dim oObject As Face
oObject = ThisApplication.CommandManager.Pick(kPartFaceFilter, "SELECCIONAR CARA BUENA")

entidades = ThisDoc.NamedEntities
entidades.SetName(oObject,"Buena")

'Dim doc = ThisApplication.ActiveDocument

'oColor = COLOR_BUENA

'oStyle = doc.RenderStyles.Item(oColor) 
'oObject.SetRenderStyle(kOverrideRenderStyle, oStyle)

undo.End
