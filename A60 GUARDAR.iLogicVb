' <FireOthersImmediately>False</FireOthersImmediately>
Dim odoc As PartDocument
odoc = ThisDoc.Document

Dim ocomp As PartComponentDefinition
ocomp = odoc.ComponentDefinition

Dim model_states As ModelStates
model_states = ocomp.ModelStates

Dim fileSystemObj As Object
fileSystemObj = CreateObject("Scripting.FileSystemObject")

Dim undo As Transaction
'undo = ThisApplication.TransactionManager.StartTransaction(odoc, "Versión de pieza")

Select Parameter("Tipo")
	Case "Rotulacion"
			Nombre_archivo = ThisDoc.FileName(False) 'without extension
			Largo_nombre_archivo = Len(Nombre_archivo)
			
			Select Largo_nombre_archivo
				Case 0
						iProperties.Value("Custom", "VDS_NumSchm") = "A60"
						iProperties.Value("Custom", "VDS_Category") = "Ingeniería"
						ThisDoc.Document.SaveAs("C:\testing.ipt", False)
						Nombre_archivo = ThisDoc.FileName(False) 'without extension
						CODIGO = Nombre_archivo
						'undo.End
				Case 9
						Prefijo = Left(Nombre_archivo, 4)
						Sufijo = Right(Nombre_archivo, 5)
						CODIGO = Prefijo & "0" & Sufijo
												
				Case 10
						CODIGO = Nombre_archivo
'											
			End Select
			MultiValue.UpdateAfterChange = True
			model_states("Principal").Activate
			CONFIG = Right(iProperties.Value("Custom", "CODIGO_ROTULACION"), 6)
			VALOR = CODIGO & "." & CONFIG
			iProperties.Value("Project", "Part Number") = CODIGO
			iProperties.Value("Project", "Description") = Parameter("CODE_CONCAT")
			iLogicVb.RunExternalRule("SACARAROS HERRAJE")
			iProperties.Value("Custom", "DESCRIPCION") = iProperties.Value("Project", "Description")
			DESCRIP = iProperties.Value("Custom", "DESCRIPCION")
			model_states.Add(DESCRIP)
			model_stateS(DESCRIP).Activate
			iProperties.Value("Project", "Part Number") = VALOR
			model_states.Item("Principal").Activate
			MessageBox.Show("CONFIGURACIÓN CREADA CORRECTAMENTE", "CONFIGURACIÓN")
			InventorVb.DocumentUpdate()
			

End Select
		
'undo.end
