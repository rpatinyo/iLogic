' <FireOthersImmediately>False</FireOthersImmediately>
AddReference "System.Data"
AddReference "System.Core"
AddReference "System.Xml"
Imports System.Data.Odbc
Imports System.Data.OleDb
Imports System.data

Sub main

parameter("TSQL") = "x_bi_sql_view_categoria_metal"
parameter("PAR") = "ACABADO_MATERIAL"
parameter("CSQL") = "x_tipoacabado"
parameter("SQL") = "Select Distinct x_bi_sql_view_categoria_metal.x_tipoacabado " &
		"From x_bi_sql_view_categoria_metal " &
		"Where (((x_bi_sql_view_categoria_metal.x_material)='" & PARAMETER("TIPO_MATERIAL") & "') and (((x_bi_sql_view_categoria_metal.x_tipoacabado) = 'TO') or ((x_bi_sql_view_categoria_metal.x_tipoacabado) = 'MZO'))) " &
		"Group By x_bi_sql_view_categoria_metal.x_tipoacabado " &
		"HAVING (COUNT(x_bi_sql_view_categoria_metal.x_tipoacabado)>=1) " &
		"Order By x_bi_sql_view_categoria_metal.x_tipoacabado ASC;"
		
		
con2(parameter("TSQL"), parameter("PAR"), parameter("CSQL"), parameter("SQL"))

End Sub




Sub con2(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList

	For Each row In t1.Rows
		
     nombre.Add(row(campo))

	Next
	
	MultiValue.List(iProp) = nombre
	
'	iProperties.Value("Custom", "ABREV_TIPO_PIEZA") = nombre(0)
'	parameter("ABREV_TIPO_PIEZA") = iProperties.Value("Custom", "ABREV_TIPO_PIEZA")
		
End Sub
