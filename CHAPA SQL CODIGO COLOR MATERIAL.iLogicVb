' <FireOthersImmediately>False</FireOthersImmediately>
AddReference "System.Data"
AddReference "System.Core"
AddReference "System.Xml"
Imports System.Data.Odbc
Imports System.Data.OleDb
Imports System.data

Sub main

parameter("TSQL") = "x_bi_sql_view_color_metal"
parameter("PAR") = "CODIGO_COLOR_MATERIAL"
parameter("CSQL") = "x_codigo"
parameter("SQL") = "Select x_bi_sql_view_color_metal.x_codigo " &
		"From x_bi_sql_view_color_metal " &
		"Where (((x_bi_sql_view_color_metal.x_descripcion)='" & parameter("COLOR_MATERIAL") & "'));"

con3(parameter("TSQL"), parameter("PAR"), parameter("CSQL"), parameter("SQL"))

iProperties.Value("Custom", "COLOR_MATERIAL") = PARAMETER("COLOR_MATERIAL")

parameter("TSQL") = "x_bi_sql_view_color_metal"
parameter("PAR") = "CODIGO_COLOR_MATERIAL_INVENTOR"
parameter("CSQL") = "x_inventor_color"
parameter("SQL") = "Select x_bi_sql_view_color_metal.x_inventor_color " &
		"From x_bi_sql_view_color_metal " &
		"Where (((x_bi_sql_view_color_metal.x_descripcion)='" & parameter("COLOR_MATERIAL") & "'));"

con2(parameter("TSQL"), parameter("PAR"), parameter("CSQL"), parameter("SQL"))

iProperties.Value("Custom", "COLOR_MATERIAL") = PARAMETER("COLOR_MATERIAL")
SPINT = Parameter("L1_DES_CHAPA") / 1000 * Parameter("L2_DES_CHAPA") / 1000 * Parameter("N_CARAS_PINTADAS")
iProperties.Value("Custom", "N_CARAS_PINTADAS") = Parameter("N_CARAS_PINTADAS")
iProperties.Value("Custom", "SPINT") = FormatNumber(CDbl(SPINT), "3", vbFalse)
End Sub


Sub con3(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList

	For Each row In t1.Rows
		
     nombre.Add(row(campo))

	Next
	
	MultiValue.List(iProp) = nombre
	Try
		iProperties.Value("Custom", "CODIGO_COLOR_MATERIAL") = nombre(0)
		parameter("CODIGO_COLOR_MATERIAL") = iProperties.Value("Custom", "CODIGO_COLOR_MATERIAL")
	Catch
	End Try
	
End Sub

Sub con2(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList

	For Each row In t1.Rows
		
     nombre.Add(row(campo))

	Next
	
	MultiValue.List(iProp) = nombre
	Try
		iProperties.Value("Custom", "CODIGO_COLOR_MATERIAL_INVENTOR") = nombre(0)
		parameter("CODIGO_COLOR_MATERIAL_INVENTOR") = iProperties.Value("Custom", "CODIGO_COLOR_MATERIAL_INVENTOR")
	Catch
	End Try
	
End Sub
