' <FireOthersImmediately>False</FireOthersImmediately>
AddReference "System.Data"
AddReference "System.Core"
AddReference "System.Xml"
Imports System.Data.Odbc
Imports System.Data.OleDb
Imports System.data

Sub main

parameter("TSQL") = "tipo_pieza"
parameter("PAR") = "TIPO_PIEZA"
parameter("CSQL") = "name"
parameter("SQL") = "Select tipo_pieza.name " &
		"From tipo_pieza " &
		"Order By tipo_pieza.name;"
			
con2(parameter("TSQL"), parameter("PAR"), parameter("CSQL"), parameter("SQL"))

'If iProperties.Value("Custom", "L1") = "" Then
	iProperties.Value("Custom", "L1") = Parameter("L1")
	iProperties.Value("Custom", "L2") = Parameter("L2")
	iProperties.Value("Custom", "L3") = Parameter("L3")
	Parameter("L1") = iProperties.Value("Custom", "L1")
	Parameter("L2") = iProperties.Value("Custom", "L2")
	Parameter("L3") = iProperties.Value("Custom", "L3")
'End If

End Sub

Sub con2(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList

	For Each row In t1.Rows
		
     nombre.Add(row(campo))

	Next
	
	MultiValue.List(iProp) = nombre
		
End Sub
