Dim odoc As PartDocument
odoc = ThisDoc.Document

Dim ocomp As PartComponentDefinition
ocomp = odoc.ComponentDefinition

Dim model_states As ModelStates
model_states = ocomp.ModelStates

Dim fileSystemObj As Object
fileSystemObj = CreateObject("Scripting.FileSystemObject")

Dim undo As Transaction
'undo = ThisApplication.TransactionManager.StartTransaction(odoc, "Versión de pieza")

Select Parameter("Tipo")
	Case "Iluminacion"
			Nombre_archivo = ThisDoc.FileName(False) 'without extension
			Largo_nombre_archivo = Len(Nombre_archivo)
			
			Select Largo_nombre_archivo
				Case 0
						iProperties.Value("Custom", "VDS_NumSchm") = "ILUMINACION"
						iProperties.Value("Custom", "VDS_Category") = "Ingeniería"
						ThisDoc.Document.SaveAs("C:\testing.ipt", False)
						Nombre_archivo = ThisDoc.FileName(False) 'without extension
						CODIGO = Nombre_archivo
						'undo.End
				Case 9
						Prefijo = Left(Nombre_archivo, 4)
						Sufijo = Right(Nombre_archivo, 5)
						CODIGO = Prefijo & "0" & Sufijo
												
				Case 10
						CODIGO = Nombre_archivo
'											
			End Select
			MultiValue.UpdateAfterChange = True
			
			model_states("Principal").Activate
		
		iProperties.Value("Project", "Part Number") = CODIGO
		CONFIG = Right(iProperties.Value("Custom", "CODIGO_ILUMINACION"), 6)
		'MessageBox.Show(CONFIG, "CONFIG")

		iProperties.Value("Custom", "CODIGO_COMPRA_ILUMINACION") = iProperties.Value("Custom", "CODIGO_ILUMINACION")
'MessageBox.Show(parameter("TIPO_ILUMINACION"), "TIPO")
		If Parameter("TIPO_ILUMINACION") = "TIRA LED" Then
			'MessageBox.Show("ENTRA EN TIRA y ejecuta barrido", "Title")

			'iProperties.Value("Custom", "LARGO_PRODUCTO_COMPRA") = Parameter("INS_LARGO") / 1000
			iLogicVb.RunExternalRule("INSCA LONGITUD BARRIDO")	
		End If
		Try
			VALOR = CODIGO & "." & CONFIG
			iProperties.Value("Project", "Description") = PARAMETER("DESCRIPCION")
			iProperties.Value("Custom", "DESCRIPCION") = iProperties.Value("Project", "Description")
			iLogicVb.RunExternalRule("SACARAROS HERRAJE")
			DESCRIP = iProperties.Value("Project", "Description")
			'MessageBox.Show(DESCRIP, "NUEVO MS")
			model_states.Add(DESCRIP)
			
			model_states(DESCRIP).Activate
			
			iProperties.Value("Project", "Part Number") = VALOR
			
			model_states.Item("Principal").Activate
			MessageBox.Show("CONFIGURACIÓN CREADA CORRECTAMENTE", "CONFIGURACIÓN")
			
		Catch
			
		End Try
			
End Select
		
'undo.end
