Dim oDoc As AssemblyDocument
oDoc = ThisDoc.Document
oPartCompDef = oDoc.ComponentDefinition
 Dim oModelStates As ModelStates
    oModelStates = oPartCompDef.ModelStates
	
    ' Get all model state names from ModelStsates object.
	Dim numeracion As New ArrayList()
	Dim sortedModelState As New ArrayList()
	Dim oModelState As ModelState
    For Each oModelState In oModelStates
		' Logger.Info(iProperties.Value("Project", "Part Number"))
		oModelState.Activate
		sortedModelState.Add(iProperties.Value("Project", "Part Number"))
		DERECHA_3 = Right(iProperties.Value("Project", "Part Number"), 3)
		DERECHA_6 = Right(iProperties.Value("Project", "Part Number"), 6)
		IZQUIERDA_3 = Left(DERECHA_6, 3)
		
		If IZQUIERDA_3 <> "HRJ" Then
			DERECHA_3 = "000"
		End If
		numeracion.Add(DERECHA_3)
		
    Next
	
'	For Each item As String In sortedModelState
'		Logger.Info("Model State Ordenados : {0}", item)
'	Next
	numeracion.Sort
	
'	For Each item As String In numeracion
'		Logger.Info("Numeración : {0}", item)
'	Next
	Elementos = numeracion.Count
	
	Propuesto = numeracion(Elementos - 1) + 1
	
	If Propuesto >=1 And Propuesto <10 Then
		Propuesto = "00" & FormatNumber(CDbl(Propuesto), "0", vbFalse)
	End If
	
	If Propuesto >=10 And Propuesto <100 Then
		Propuesto = "0" & FormatNumber(CDbl(Propuesto), "0", vbFalse)
	End If
	oModelStates("Principal").Activate
	iProperties.Value("Custom", "CONFIG") = "HRJ" & Propuesto
