' <FireOthersImmediately>False</FireOthersImmediately>
AddReference "System.Data"
AddReference "System.Core"
AddReference "System.Xml"
Imports System.Data.Odbc
Imports System.Data.OleDb
Imports System.data

Sub main
parameter("TSQL") = "product_category"
parameter("PAR") = "CATEGORIA"
parameter("CSQL") = "complete_name"
parameter("SQL") = "Select product_template.default_code " &
", product_template.name " &
", product_template.description " &
", product_category.complete_name " &
"From product_template INNER Join product_category On product_template.categ_id = product_category.id " &
"Where (((product_template.technical_office)='1') AND product_template.default_code = '" & parameter("CODIGO_CONFIG") & "') " &
"Order By product_template.default_code;"
con2(parameter("TSQL"),parameter("PAR"),parameter("CSQL"),parameter("SQL"))
	
End Sub




Sub con2(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList

	For Each row In t1.Rows
		
     nombre.Add(row(campo))

	Next
	
	MultiValue.List(iProp) = nombre
			
	iProperties.Value("Custom", "CATEGORIA")= nombre(0)
	parameter("CATEGORIA") = iProperties.Value("Custom", "CATEGORIA")
	final = Len(iProperties.Value("Custom", "CATEGORIA"))
	Extraccion = final - 13
	Categ = Mid(iProperties.Value("Custom", "CATEGORIA"), 14, Extraccion)
	iProperties.Value("Custom", "00 Categoria PTERMINADO") = Categ
	'Se modifica el campo de Odoo "technical_office"
	'iProperties.Value("Custom", "technical_office") = "0"
	'Se asigna a la categoría de Vault "Ingeniería"
	iProperties.Value("Custom", "VDS_Category") = "Ingeniería"
	'Se desactiva el esquema de numeración
	iProperties.Value("Custom", "VDS_NumSchm") = ""
	
	
	
End Sub
