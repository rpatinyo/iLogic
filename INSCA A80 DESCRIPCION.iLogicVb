' <FireOthersImmediately>False</FireOthersImmediately>
AddReference "System.Data"
AddReference "System.Core"
AddReference "System.Xml"
Imports System.Data.Odbc
Imports System.Data.OleDb
Imports System.data

Sub main

parameter("TSQL") = "a80_a80"
parameter("PAR") = "DESCRIPCION"
parameter("CSQL") = "name"
parameter("SQL") = "Select distinct a80_a80.name " &
		"From a80_a80 INNER Join a80_type On a80_a80.type = a80_type.id " &
		"Where (a80_type.name = '" & parameter("TIPO_A80") & "')" &
		"Group by (a80_a80.name) " &
		"Having ((Count(a80_a80.name)>=1));"
		
con2(parameter("TSQL"), parameter("PAR"), parameter("CSQL"), parameter("SQL"))

End Sub




Sub con2(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList

	For Each row In t1.Rows
		
     nombre.Add(row(campo))

	Next
	
	MultiValue.List(iProp) = nombre
		
	iProperties.Value("Custom", "DESCRIPCION_A80") = nombre(0)
	parameter("DESCRIPCION") = iProperties.Value("Custom", "DESCRIPCION_A80")
	
	
'	iProperties.Value("Project", "Description") = nombre(0)
'	iProperties.Value("Custom", "DESCRIPCION_HERRAJE") = iProperties.Value("Project", "Description")
	'iLogicVb.RunRule("CONEXION_CÓDIGO")
End Sub
