' <FireOthersImmediately>False</FireOthersImmediately>
AddReference "System.Data"
AddReference "System.Core"
AddReference "System.Xml"
Imports System.Data.Odbc
Imports System.Data.OleDb
Imports System.data

Sub main

parameter("TSQL") = "product_template"
parameter("PAR") = "VAULT_ID"
parameter("CSQL") = "vault_internal_id"
parameter("SQL") = "Select product_product.default_code" &
", product_template.vault_internal_id" &
", product_product.active " &
"From product_product INNER Join product_template On product_product.product_tmpl_id = product_template.id " &
"Where (((product_product.default_code)= '" & parameter("CODIGO_CONFIG") & "') AND (product_product.active = '1')) " &
"Order By product_template.vault_internal_id DESC;"
con2(parameter("TSQL"),parameter("PAR"),parameter("CSQL"),parameter("SQL"))
	
End Sub




Sub con2(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList
	
	nombre.Clear()
	MultiValue.List(iProp) = nombre
	
	For Each row In t1.Rows
		nombre.Add(row(campo))
		'Logger.Debug("notas = {0}", nombre(0).ToString)
	Next
	
	If nombre(0).ToString = "" Then
		iProperties.Value("Custom", "VAULT_ID") = "0"
	ElseIf nombre(0).ToString <> "" Then
		iProperties.Value("Custom", "VAULT_ID") = nombre(0).ToString
	End If
	
	MultiValue.List(iProp) = nombre
		
	parameter("VAULT_ID") = iProperties.Value("Custom", "VAULT_ID")
	
	
	If iProperties.Value("Custom", "VAULT_ID") <> "0" Then
		iProperties.Value("Custom", "BANNER") = "EL PRODUCTO YA SE HA DIBUJADO ANTERIORMENTE. CONSULTAR VAULT"
		Else
			iProperties.Value("Custom", "BANNER") = ""
	End If

	
End Sub
