' <FireOthersImmediately>False</FireOthersImmediately>
AddReference "System.Data"
AddReference "System.Core"
AddReference "System.Xml"
Imports System.Data.Odbc
Imports System.Data.OleDb
Imports System.data

Sub main
iLogicVb.RunExternalRule("ENCOLADO SQL TIPO PIEZA")

If Parameter("TIPO_PIEZA") = "" Then
	parameter("TIPO_PIEZA") = "0_N#A"
End If
	parameter("TSQL") = "tipo_pieza"
	parameter("PAR") = "ABREV_TIPO_PIEZA"
	parameter("CSQL") = "abreviatura"
	parameter("SQL") = "Select tipo_pieza.abreviatura " &
	"From tipo_pieza " &
	"Where (((tipo_pieza.name)='" & parameter("TIPO_PIEZA") & "'));"
	con2(parameter("TSQL"), parameter("PAR"), parameter("CSQL"), parameter("SQL"))
	iLogicVb.RunExternalRule("ENCOLADO SQL MEDIDAS")


'	Parameter("L1") = iProperties.Value("Custom", "L1")
'	Parameter("L2") = iProperties.Value("Custom", "L2")
'	Parameter("L3") = iProperties.Value("Custom", "L3")
	
	
	LL = iProperties.Value("Custom", "L1")
	LA = iProperties.Value("Custom", "L2")
	LE = iProperties.Value("Custom", "L3")
	
If parameter("MALLA") = 0 Or parameter("MALLA") = 1 Then
	desc = iProperties.Value("Custom", "ABREV_TIPO_PIEZA") & " " & LL & "x" & LA & "x" & LE & "mm"
	Else
		desc = iProperties.Value("Custom", "ABREV_TIPO_PIEZA") & " " & LA & "x" & LL & "x" & LE & "mm"
End If
	
iProperties.Value("Project", "Description") = desc
iLogicVb.RunExternalRule("INSCA PESO ENSAMBLAJE")

End Sub

Sub con2(tabla As String, iProp As String, campo As String, BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
	'	Dim MDBConnString_ As String = "DRIVER={PostgreSQL Unicode(x64)};SERVER=mail.insca.com;PORT=5432;DATABASE=base;UID=insca;PWD=insca2021; Persist Security Info=False;"
	Dim ds As New DataSet


	'	Dim cnn As OleDbConnection = New OleDbConnection(MDBConnString_)
	Dim cnn As OdbcConnection = New OdbcConnection(MDBConnString_)


	cnn.Open()
	Dim cmd As New OdbcCommand(query, cnn)
	Dim da As New OdbcDataAdapter(cmd)
	da.Fill(ds, tabla)

	cnn.Close()
	Dim t1 As DataTable = ds.Tables(tabla)
	Dim row As DataRow

	Dim nombre As New ArrayList

	For Each row In t1.Rows

		nombre.Add(row(campo))

	Next

	MultiValue.List(iProp) = nombre

	iProperties.Value("Custom", "ABREV_TIPO_PIEZA") = nombre(0)
	parameter("ABREV_TIPO_PIEZA") = iProperties.Value("Custom", "ABREV_TIPO_PIEZA")

End Sub
