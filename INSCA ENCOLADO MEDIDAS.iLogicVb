Dim odoc As AssemblyDocument
odoc = ThisApplication.ActiveDocument
odef = odoc.ComponentDefinition
Dim vX, vy, vz As Double

vX = Math.Abs(odef.RangeBox.MaxPoint.X - odef.RangeBox.MinPoint.X) * 10
vy= Math.Abs(odef.RangeBox.MaxPoint.Y - odef.RangeBox.MinPoint.Y) * 10
vz = Math.Abs(odef.RangeBox.MaxPoint.Z - odef.RangeBox.MinPoint.Z) * 10

PARAMETER("L1") = vX
PARAMETER("L2") = vy
PARAMETER("L3") = vz

MAXIMO = MaxOfMany(PARAMETER("L1"),PARAMETER("L2"))
MINIMO = MinOfMany(PARAMETER("L1"), PARAMETER("L2"))


If iProperties.Value("Custom", "Pintar_cantos") = True Then

	Parameter("SUPERFICIE_CANTOS_PINTADO")= (Parameter("PINTAR_CANTOS_LARGO") * (MAXIMO / 1000) * (PARAMETER("L3") / 1000)) + (Parameter("PINTAR_CANTOS_CORTO") * (MINIMO / 1000) * (PARAMETER("L3") / 1000))
	iProperties.Value("Custom", "NRO_CANTOS_PINTADO") = Parameter("PINTAR_CANTOS_LARGO") & "CL+" & Parameter("PINTAR_CANTOS_CORTO") & "CC"
	Else
	
	Parameter("PINTAR_CANTOS_LARGO") = 0
	Parameter("PINTAR_CANTOS_CORTO") = 0
	Parameter("SUPERFICIE_CANTOS_PINTADO") = 0
	
	iProperties.Value("Custom", "NRO_CANTOS_PINTADO") = 0 & "CL+" & 0 & "CC"

End If


If iProperties.Value("Custom", "Chapar_cantos") = True Then

Parameter("LONG_CANTOS") = (Parameter("CANTOS_LARGO") * MAXIMO) + (Parameter("CANTOS_CORTO") * MINIMO)
iProperties.Value("Custom", "NRO_CANTOS") = Parameter("CANTOS_LARGO") & "CL+" & Parameter("CANTOS_CORTO") & "CC"

Else
	
Parameter("CANTOS_LARGO") = 0
Parameter("CANTOS_CORTO") = 0
Parameter("LONG_CANTOS") = 0

iProperties.Value("Custom", "NRO_CANTOS") = "0" & "CL+" & "0" & "CC"


End If


If iProperties.Value("Custom", "Chapar_cantos") = True Then

Parameter("LONG_CANTOS") = (Parameter("CANTOS_LARGO") * MAXIMO) + (Parameter("CANTOS_CORTO") * MINIMO)
iProperties.Value("Custom", "NRO_CANTOS") = Parameter("CANTOS_LARGO") & "CL+" & Parameter("CANTOS_CORTO") & "CC"

Else
	
Parameter("CANTOS_LARGO") = 0
Parameter("CANTOS_CORTO") = 0
Parameter("LONG_CANTOS") = 0

iProperties.Value("Custom", "NRO_CANTOS") = "0" & "CL+" & "0" & "CC"

End If

If iProperties.Value("Custom", "Pintar") = True Then

iProperties.Value("Custom", "SPINT") = Round(((Parameter("N_CARAS_PINTADAS") * Parameter("L1") * Parameter("L2")) / 1000000), 3)


NRO_CARAS_PINT = Parameter("N_CARAS_PINTADAS")
iProperties.Value("Custom", "NRO_CARAS_PINTADAS") = NRO_CARAS_PINT


Else

iProperties.Value("Custom", "SPINT") = 0
NRO_CARAS_PINT = 0
iProperties.Value("Custom", "NRO_CARAS_PINTADAS") = NRO_CARAS_PINT

End If

RuleParametersOutput()
InventorVb.DocumentUpdate()
