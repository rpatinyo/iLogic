' <FireOthersImmediately>False</FireOthersImmediately>
	
MultiValue.UpdateAfterChange = True

Dim odoc As AssemblyDocument
odoc = ThisDoc.Document
ocomp = odoc.ComponentDefinition
Dim model_states As ModelStates
model_states = ocomp.ModelStates

Dim fileSystemObj As Object
fileSystemObj = CreateObject("Scripting.FileSystemObject")

Dim undo As Transaction
'undo = ThisApplication.TransactionManager.StartTransaction(odoc, "Versión de pieza")

	Select Parameter("Tipo")
		Case "A00 SQL"
			Nombre_archivo = ThisDoc.FileName(False) 'without extension
			Largo_nombre_archivo = Len(Nombre_archivo)

			Select Largo_nombre_archivo
				Case 0
					iProperties.Value("Custom", "VDS_Category") = "Ingeniería"
					RUTA = ThisDoc.WorkspacePath
					ThisDoc.Document.SaveAs(RUTA & Parameter("CODIGO_CONFIG") & ".iam", False)
					Nombre_archivo = ThisDoc.FileName(False) 'without extension
					CODIGO = Nombre_archivo
					'undo.End
				
				Case 16
					MessageBox.Show("CÓDIGO ANTIGUO. RENOMBRAR EN VAULT", "ERROR",MessageBoxButtons.OK,MessageBoxIcon.Error)
					Return

				Case 17
					CODIGO = parameter("CODIGO_CONFIG")
					
				Case Else					
					MessageBox.Show("CÓDIGO ANTIGUO. RENOMBRAR EN VAULT", "ERROR",MessageBoxButtons.OK,MessageBoxIcon.Error)
					Return

			End Select
			MultiValue.UpdateAfterChange = True
			
			model_states("Principal").Activate
			VALOR = CODIGO
			iProperties.Value("Project", "Part Number") = CODIGO & "#PRINCIPAL"
			iLogicVb.RunExternalRule("SACARAROS NOTAS")
			DESCRIP = iProperties.Value("Custom", "NOTAS")
			POSICION = InStr(1, DESCRIP, vbCrLf, 1)
			LARGO = Len(DESCRIP)
			'DESCRIP = CODIGO & "-" & Mid(DESCRIP, POSICION, LARGO - POSICION +1)
			DESCRIP = VALOR
			Try
				model_states.Add(DESCRIP)
				model_stateS(DESCRIP).Activate
				iProperties.Value("Project", "Part Number") = VALOR
				iProperties.Value("Project", "Description") = PARAMETER("DESCRIPCION")
				iLogicVb.RunExternalRule("INSCA EMBALAJE")
				iLogicVb.RunExternalRule("CADENA BUSQUEDA")
				model_states.Item("Principal").Activate
				MessageBox.Show("CONFIGURACIÓN CREADA CORRECTAMENTE", "CONFIGURACIÓN")
				InventorVb.DocumentUpdate()
				
			Catch
			End Try
					
	End Select
	iLogicVb.RunExternalRule("A00 SQL TECHNICAL OFFICE")
	ThisDoc.Save
	InventorVb.DocumentUpdate()
