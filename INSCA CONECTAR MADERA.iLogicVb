AddReference "System.Data"
AddReference "System.Core"
AddReference "System.Xml"
Imports System.Data.Odbc
Imports System.Data.OleDb
Imports System.Data
Imports system.Windows.Forms


Sub MAIN()
Conexion("x_bi_sql_view_categoria_madera", "MAT", 6)
Conexion("x_bi_sql_view_categoria_madera", "ACABADO", 7)
Conexion("x_bi_sql_view_categoria_madera", "MEDIDAS", 8)
Conexion("x_bi_sql_view_categoria_madera", "DESC", 9)
Conexion("x_bi_sql_view_categoria_madera", "CODIGO_VIRTUAL_MADERA", 10)
Conexion("x_bi_sql_view_categoria_madera", "MAT_CODE", 11)
Conexion("x_bi_sql_view_categoria_madera", "DENSIDAD_ODOO", 12)

Conexion("x_bi_sql_view_cantos", "MAT_CANTOS", 6)
Conexion("x_bi_sql_view_cantos", "ACABADO_CANTOS", 7)
Conexion("x_bi_sql_view_cantos", "MEDIDAS_CANTOS", 8)
Conexion("x_bi_sql_view_cantos", "DESC_CANTOS", 9)
Conexion("x_bi_sql_view_cantos", "P_CANTOS_CODE", 10)

Conexion("wood_config", "WOOD_CONFIG", 10)
Conexion("wood_config", "WOOD_CONFIG_CODE", 1)


Conexion("x_bi_sql_view_color_madera", "COL", 6)
Conexion("x_bi_sql_view_color_madera", "COL_CODE", 7)

Conexion("x_bi_sql_view_color_madera", "COL_CANTOS", 6)
Conexion("x_bi_sql_view_color_madera", "COL_CANTOS_CODE", 7)

Conexion("Tipo_pieza", "DETIPO_DESC", 1)
Conexion("Tipo_pieza", "DETIPO_CODE", 2)



Filtro("MAT", "F_MAT")
Filtro("MAT_CANTOS","F_MAT_CANTOS")

End Sub



Sub Conexion(tabla As String, iProp As String,campo As Integer)

	Dim Table_ As String = tabla
	Dim query As String = "SELECT * FROM " & Table_
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList

	For Each row In t1.Rows
		
     nombre.Add(row(campo))

	Next
	
	MultiValue.List(iProp) = nombre

End Sub


Sub Filtro(prop As String, prop_filtrada As String)

array_prop = MultiValue.List(prop)
array_fprop = MultiValue.List(prop_filtrada)

For Each valor In array_prop
	If array_fprop.Contains(valor) Then
	Else

		array_fprop.Add(valor)
	End If
Next

MultiValue.List(prop_filtrada) = array_fprop


End Sub
