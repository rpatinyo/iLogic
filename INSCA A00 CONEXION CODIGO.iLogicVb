' <FireOthersImmediately>False</FireOthersImmediately>
AddReference "System.Data"
AddReference "System.Core"
AddReference "System.Xml"
Imports System.Data.Odbc
Imports System.Data.OleDb
Imports System.data

Sub main
PARAMETER("TSQL") = "product_template"
PARAMETER("PAR") = "CODIGO_CONFIG"
PARAMETER("CSQL") = "default_code"
PARAMETER("SQL") = "Select product_template.default_code " &
", product_template.name " &
", product_template.description " &
", product_category.complete_name " &
"From product_template INNER Join product_category On product_template.categ_id = product_category.id " &
"Where (((product_template.technical_office)='1')) " &
"Order By product_template.default_code ASC;"
con2(PARAMETER("TSQL"), PARAMETER("PAR"), PARAMETER("CSQL"), PARAMETER("SQL"))


	
End Sub




Sub con2(tabla As String, iProp As String,campo As String,BUSQUEDA As String)

	Dim Table_ As String = tabla
	Dim query As String = CType(BUSQUEDA, String)
	Dim MDBConnString_ As String = "DRIVER={PostgreSQL Unicode(x64)};SERVER=172.31.30.244;PORT=5432;DATABASE=base;UID=insca;PWD=insca2021; Persist Security Info=False;"
'	Dim MDBConnString_ As String = "DRIVER={PostgreSQL Unicode(x64)};SERVER=mail.insca.com;PORT=5432;DATABASE=base;UID=insca;PWD=insca2021; Persist Security Info=False;"
	Dim ds As New DataSet
	
	
'	Dim cnn As OleDbConnection = New OleDbConnection(MDBConnString_)
	Dim cnn As OdbcConnection = New OdbcConnection(MDBConnString_) 
	
	
	cnn.Open()
    Dim cmd As New OdbcCommand(query, cnn)
	Dim da As New OdbcDataAdapter(cmd)
	da.Fill(ds,tabla)

	cnn.Close()
	Dim t1 As DataTable = ds.Tables(tabla)
	Dim row As DataRow
	
	Dim nombre As New ArrayList

	For Each row In t1.Rows
		
     nombre.Add(row(campo))

	Next
	
	MultiValue.List(iProp) = nombre
	iProperties.Value("Custom", "CODIGO_CONFIG")= nombre(0)
	
	iProperties.Value("Custom", "CODIGO_CONFIG") = PARAMETER("CODIGO_CONFIG")
	PARAMETER("CODIGO") = Left(iProperties.Value("Custom", "CODIGO_CONFIG"), 10)
	PARAMETER("CONFIG") = Right(iProperties.Value("Custom", "CODIGO_CONFIG"), 6)
  	iProperties.Value("Custom", "CÓDIGO") = PARAMETER("CODIGO")
  	iProperties.Value("Custom", "CONFIG") = PARAMETER("CONFIG")
	
	
End Sub
